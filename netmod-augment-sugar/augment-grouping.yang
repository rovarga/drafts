module augment-grouping {
    yang-version 1;
    namespace "urn:ietf:params:xml:ns:yang:ietf-grpaug";
    prefix ag;

    organization
        "IETF NETMOD (NETCONF Data Modeling Language) Working Group";

    contact
        "WG Web:   <http://tools.ietf.org/wg/netmod/>
        WG List:  <mailto:netmod@ietf.org>

        WG Chair: Thomas Nadeau
                  <mailto:tnadeau@lucidvision.com>

        WG Chair: Juergen Schoenwaelder
                  <mailto:j.schoenwaelder@jacobs-university.de>

        WG Chair: Kent Watsen
                  <mailto:kwatsen@juniper.net>

        Editor:   Robert Varga
                  <mailto:robert.varga@pantheon.sk>";

    description
        "This module defines augment-grouping, a YANG language extension
         for attaching augment statements to a grouping definition.

         Copyright (c) 2015 IETF Trust and the persons identified as
         authors of the code. All rights reserved.
 
         Redistribution and use in source and binary forms, with or
         without modification, is permitted pursuant to, and subject to
         the license terms contained in, the Simplified BSD License set
         forth in Section 4.c of the IETF Trust's Legal Provisions
         Relating to IETF Documents
         (http://trustee.ietf.org/license-info).
 
         The key words 'MUST', 'MUST NOT', 'REQUIRED', 'SHALL', 'SHALL
         NOT', 'SHOULD', 'SHOULD NOT', 'RECOMMENDED', 'MAY', and
         'OPTIONAL' in the module text are to be interpreted as described
         in RFC 2119 (http://tools.ietf.org/html/rfc2119).
 
         This version of this YANG module is part of RFC XXXX
         (http://tools.ietf.org/html/rfcXXXX); see the RFC itself for
         full legal notices."

    revision 2016-02-03 {
        description
            "Initial revision.";
        reference
            "RFC XXXX: YANG Extension for augmenting groupings";
    }

    extension "augment-grouping" {
        description
            "Defines a set of augment statements to be attached to the grouping
             identified by the argument. An instance of this extension can
             carry one or more augment statements, which will be applied to
             each instantiation of the target grouping.

             The argument of these augment statements must be a relative path,
             not an absolute and its target must lie within the grouping or
             augmentations introduced by other modules using this extension.

             Argument value of \".\" indicates that the container (or list)
             in which the grouping is being instantiated is to be augmented.

             All nodes introduced via this extension will have the namespace
             of the module where this extension is used, e.g. the effective
             data model is the same as if the module used explicit augment
             for every instantiation of the target grouping present known in
             the system.";
        argument "target-grouping";
        reference
            "RFC XXXX Section YY, augment-grouping Extension Statement";
    }

    feature "augment-grouping" {
        description
            "Indicates that the server supports augment-grouping extension
             and its effective data model reflects augment statement
             expansion as specified by this extension.";
        reference
            "RFC XXXX Section ZZ, augment-grouping Feature";
    }
}
